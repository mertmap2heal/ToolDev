# Avionics Subsystem Spec

# Specification: Avionics Subsystem Spec

## POL-REQ-100: Power budget requirement
The subsystem power draw budget:
| Mode | Watts |
| --- | --- |
| Idle | 12 |
- Weight: 42
- Margin: 0.125
- Safety Critical: true
- Reviewed On: 2026-01-15T00:00:00.000Z

### POL-REQ-101: Idle power requirement
Idle power draw shall not exceed 12 W.
- Safety Critical: false
- Derived From -> POL-REQ-100
