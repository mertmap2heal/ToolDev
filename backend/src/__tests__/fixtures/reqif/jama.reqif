# Landing Gear V&V

# Specification: Landing Gear V&V

## jso-req-1: JAMA-FR-1 (Functional Requirement)
The landing gear shall fully deploy within 10 seconds.

## jso-tc-1: JAMA-TC-1 (Test Case)
Measure gear deploy time with a calibrated stopwatch.
- Verifies -> jso-req-1
