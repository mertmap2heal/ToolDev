# Flight Control Requirements

# Specification: Flight Control Module

## DOORS-SYS-1: System parent requirement
The aircraft shall maintain controlled flight.
- Priority: high

### DOORS-SUB-1: Child requirement A
The flight control surfaces shall respond within 50 ms.
- Priority: low
- Satisfies -> DOORS-SYS-1

### DOORS-SUB-2: Child requirement B
The system shall log all control inputs.
- Satisfies -> DOORS-SYS-1
